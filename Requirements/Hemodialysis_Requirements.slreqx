# Hemodialysis_Requirements

## Hemodialysis_Requirements!Sheet1: References to Hemodialysis_Requirements.xlsx (Sheet1) (Container)
Read-only references to Microsoft Excel document.

### 1: Architecture (Functional)
This is software architecture requirements

### 1.1: Command Inputs (Functional)

### 1.1.1: Patient Information (Functional)
UI/Controller shall have the capability to enter patient information such as weight, BP, Age etc

### 1.1.2: Plasma Refill Rate (Functional)
UI shall have the way to define PPR as constant or some slope depending on patient's history

### 1.2: Feedback Inputs (Functional)

### 1.2.1: Calculated UFR (Functional)
Relative blood volume shall be calculated from calculated UFR and PPR

### 2: Supervisory Logic/Controller (Functional)
This is hemodialysis equipment controller requirements

### 2.1: UFR monitoring system (Functional)
Control system shall maintain mean UFR -- 0.17 +/- 0.06 ml/sec for longer sessions and 0.15 +/- 0.05 for shorter sessions

### 2.2: Prevent Interdialytic Hypotension (Functional)
Control system shall stop UFR when rate of change of relative blood volume changes below or above critical levels

### 2.3: Interface (Functional)
Control system shall receive precribed Ultrafiltration rate, relative blood volume as input from other subsystems

### 3: Fault Detector (Functional)

### 3.1: No fluid removal (Functional)
Control system shall detect and notify condition when plasma refill rate is same or faster than ultrafiltration rate

### 3.2: Prevent patient mortality (Functional)
Control system shall detect, notify and stop UF system when relative blood volume drops too rapidly (UF rate too fast than PPR) and drops below critical thresholds
